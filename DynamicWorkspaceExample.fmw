FME workspace DynamicWorkspaceExample.fmw
Title: DynamicWorkspaceExample
Description: This workspace is an example of a Dynamic workspace.
It reads in an external Excel spreadsheet listing a database and tables which to read (which is a File Geodatabase), then writes out the data to a SQLite database.
Created by Gavin Jeter, LOCUS
History: 2025-04-03,G Jeter,Initial Creation

Creator
    GEOMTYPE = Geometry Object
    NUM = 1
    CREATED -> FeatureReader_2 [INITIATOR]
    CREATED -> FeatureReader_3 [INITIATOR]
Note: Entire Database
FeatureReader_3
    ATTR_ACCUM_MODE = Only Use Result
    CLIP_TO_ENVELOPE = NO
    COMBINE_GEOM = Use Result
    DATASET = C:\FMETrainingData\Data\CommunityMapping\CommunityMap.gdb
    FILEGDB_FILEGDB_EXPOSE_FORMAT_ATTRS = fme_basename,text(50) fme_dataset,text(50) fme_feature_type,text(50)
    FILEGDB_QUERY_FEATURE_TYPES_FOR_MERGE_FILTERS = Yes
    FILEGDB_REMOVE_FEATURE_DATASET = NO
    FILEGDB_SIMPLE_DONUT_GEOMETRY = simple
    FILEGDB_STRIP_GUID_GLOBALID_BRACES = no
    FILEGDB_USE_SEARCH_ENVELOPE = NO
    FORMAT = FILEGDB
    INITIATOR_FIRST_OUTPUT = default
    INTERACT = NONE
    ORDER_RESULTS = No
    OUTPUT_ADD_SCHEMA_ATTRIBUTES = NO
    OUTPUT_FEATURES_DISPLAY = Schema and Data Features
    <SCHEMA> -> FeatureMerger_2 [SUPPLIER]
    <OTHER> -> AttributeExposer_2
AttributeExposer_2
    ATTR_TABLE = fme_dataset,,fme_basename,,fme_feature_type,
    -> FeatureMerger_2 [REQUESTOR]
Note: Merge Features to Schema
Note: Switch Me Back-and-Forth between FeatureMerger and FeatureMerger_2 to see the difference in the output
FeatureMerger_2
    ATTR_ACCUM_MODE = Merge Supplier
    ATTR_CONFLICT_RES_LOOKUP = REQUESTOR_IF_CONFLICT
    IGNORE_NULLS = No
    JOIN_KEYS = @Value(fme_feature_type) @Value(fme_feature_type_name) AUTO
    MERGE_TYPE = Attributes Only
    PROCESS_DUPS = NO
    REJECT_NULL_MISSING_KEYS = No
    SUPPLIERS_FIRST = No
    ATTR_CONFLICT_RES = Use Requestor
    MERGED -> FeatureWriter [<Generic>]
Note: This Writer could also be dynamic based on the Control Table (Excel Table) - You just need a field for the name of the file.
Note: Creates "Backup" SQLite database
FeatureWriter
    DATASET = $(FME_MF_DIR_USERTYPED)\CommunityMap.sqlite
    DATASET_ATTR = _dataset
    FEATURE_TYPE_LIST_ATTR = _feature_types
    FORMAT = SQLITE3
    SQLITE3_COORDINATE_SYSTEM_GRANULARITY = FEATURE
    SQLITE3_DESTINATION_DATASETTYPE_VALIDATION = Yes
    SQLITE3_ENCODING = utf-8
    SQLITE3_OVERWRITE_FILE = Yes
    SQLITE3_SUPPORT_INTERNATIONALIZATION = YES
    SQLITE3_TRANSACTION_INTERVAL = 500
    SQLITE3_WRITER_MODE = INSERT
    TOTAL_FEATURES_WRITTEN_ATTR = _total_features_written
Note: External Control / Say, Metadata Table
FeatureReader_2
    ATTRIBUTES = Sheet1,"Repo,Workspace,Connection,Database,Table"
    ATTR_ACCUM_MODE = Only Use Result
    CLIP_TO_ENVELOPE = NO
    COMBINE_GEOM = Use Result
    DATASET = $(FME_MF_DIR_USERTYPED)\_MainTable.xlsx
    FORMAT = XLSXR
    GEOMETRY_TYPES = Sheet1,""",fme_point"""
    INITIATOR_FIRST_OUTPUT = default
    INTERACT = NONE
    ORDER_RESULTS = No
    OUTPUT_ADD_SCHEMA_ATTRIBUTES = NO
    OUTPUT_FEATURES_DISPLAY = Schema and Data Features
    XLSXR_ALLOW_DOLLAR_SIGNS = YES
    XLSXR_APPLY_FILTERS = No
    XLSXR_CASE_SENSITIVE_FEATURE_TYPES = YES
    XLSXR_CREATE_FEATURE_TABLES_FROM_DATA = Yes
    XLSXR_EXCEL_COL_NAMES = YES
    XLSXR_EXPANDED_DATES_SCANNING = No
    XLSXR_EXPAND_MERGED_CELLS = Yes
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA_HANDLING_REVISION = 2
    XLSXR_SKIP_EMPTY_ROWS = YES
    XLSXR_STRIP_SHEETNAME_SPACES = YES
    XLSXR_TRIM_ATTR_NAME_WHITESPACE = Yes
    XLSXR_USE_CUSTOM_SCHEMA = NO
    Sheet1 -> FeatureReader [INITIATOR]
Note: Dynamic Reader based on Input Data (from FeatureReader_2)
FeatureReader
    ATTR_ACCUM_MODE = Only Use Result
    CLIP_TO_ENVELOPE = NO
    COMBINE_GEOM = Use Result
    DATASET = @Value(Database)
    FEATURETYPES = @Value(Table)
    FORMAT = GENERIC
    GENERIC_REAL_FORMAT = GUESS_FROM_EXTENSION
    INITIATOR_FIRST_OUTPUT = default
    INTERACT = NONE
    ORDER_RESULTS = No
    OUTPUT_ADD_SCHEMA_ATTRIBUTES = NO
    OUTPUT_FEATURES_DISPLAY = Schema and Data Features
    <SCHEMA> -> FeatureMerger [SUPPLIER]
    <OTHER> -> AttributeExposer
AttributeExposer
    ATTR_TABLE = fme_dataset,,fme_basename,,fme_feature_type,
    -> FeatureMerger [REQUESTOR]
Note: Merge Features to Schema
FeatureMerger
    ATTR_ACCUM_MODE = Merge Supplier
    ATTR_CONFLICT_RES_LOOKUP = REQUESTOR_IF_CONFLICT
    IGNORE_NULLS = No
    JOIN_KEYS = @Value(fme_feature_type) @Value(fme_feature_type_name) AUTO
    MERGE_TYPE = Attributes Only
    PROCESS_DUPS = NO
    REJECT_NULL_MISSING_KEYS = No
    SUPPLIERS_FIRST = No
    ATTR_CONFLICT_RES = Use Requestor
